FME workspace BDP8.fmw

Parameters:
- SourceDataset_GEOTIFF_3 = C:\Users\ppowr\Downloads\ras250_gb\data\*.tif   # Source GeoTIFF File(s) or URL(s)
- SourceDataset_OGCGEOPACKAGE = C:\Users\ppowr\Downloads\bdline_gpkg_gb\Data\bdline_gb.gpkg   # GeoPackage File
- DestDataset_POSTGIS_RASTER_3 = Postgres   # Connection
- DestDataset_GEODATABASE_FILE_3 = Results   # File Geodatabase
- DestDataset_FILEGDB = Extends   # File Geodatabase

Readers:
- GEOTIFF_2: GEOTIFF from $(SourceDataset_GEOTIFF_3)
- OGCGEOPACKAGE_1: OGCGEOPACKAGE from $(SourceDataset_OGCGEOPACKAGE)

Writers:
- GEODATABASE_FILE_2: GEODATABASE_FILE to $(DestDataset_GEODATABASE_FILE_3)
- POSTGIS_RASTER_2: POSTGIS_RASTER to $(DestDataset_POSTGIS_RASTER_3)
- FILEGDB_1: FILEGDB to $(DestDataset_FILEGDB)

Bookmark: Zad2
GEOTIFF (reader GEOTIFF_2)
    -> Reprojector
    -> RasterMosaicker
Reprojector
    DEST = EPSG:4326
    INTERPOLATION_TYPE_NAME = Nearest Neighbor
    RASTER_CELL_SIZE = Preserve Cells
    RASTER_TOLERANCE = 0.0
    SOURCE = EPSG:27700
    REPROJECTED -> RasterExtentsCoercer
RasterExtentsCoercer
    EXTENTS_TYPE = Raster Extents
    EXTENTS -> FilePropertyExtractor
FilePropertyExtractor
    FMT = FME Date/Time (%Y%m%d%H%M%S)
    PATH = @Value(fme_dataset)
    -> AttributeCreator
AttributeCreator
    ATTR_TABLE = SET_TO NewName (varchar(200)) = @Value(fme_basename)_@Value(_file_size)
    -> Inspector
    -> Extends (writer FILEGDB_1)
Extends (writer FILEGDB_1)
    attributes: Name text(100), Area_Code text(3), Area_Description text(50), File_Name text(100), Feature_Serial_Number int, Collection_Serial_Number int, Global_Polygon_ID int, Admin_Unit_ID int, Census_Code text(9), Hectares double, Non_Inland_Area double, Area_Type_Code text(2), Area_Type_Description text(25), Non_Area_Type_Code text(3), Non_Area_Type_Description text(36), fid text(20)
Inspector

Bookmark: Zad3
RasterMosaicker
    ACCUM_ATTRS_NAME = Use Attributes From One Feature
    INTERPOLATION_TYPE_NAME = Nearest Neighbor
    MERGE_PALETTES_NAME = Yes
    NODATA_OVERWRITE = No
    OVERLAPPING_VALUES = last
    SNAPPING_TYPE_NAME = Resample
    -> Reprojector_3
Reprojector_3
    DEST = EPSG:4326
    INTERPOLATION_TYPE_NAME = Nearest Neighbor
    RASTER_CELL_SIZE = Preserve Cells
    RASTER_TOLERANCE = 0.0
    SOURCE = EPSG:27700
    REPROJECTED -> RasterTiler
RasterTiler
    FORCE_EQUAL_SIZED_TILES = No
    NUM_HORIZONTAL_TILES = 7
    NUM_HORIZONTAL_TILES_ATTRIBUTE = _num_tile_columns
    NUM_VERTICAL_TILES = 13
    NUM_VERTICAL_TILES_ATTRIBUTE = _num_tile_rows
    RASTER_INDEX_ATTRIBUTE = _raster_index
    TILESIZE_OR_NUMTILES = Number of Tiles
    TILE_COLUMN_ATTRIBUTE = _tile_column
    TILE_ROW_ATTRIBUTE = _tile_row
    TILES -> SpatialFilter [Candidate]
scotland_and_wales_region (reader OGCGEOPACKAGE_1)
    attributes: Name text(100), Area_Code text(3), Area_Description text(50), File_Name text(100), Feature_Serial_Number mediumint, Collection_Serial_Number mediumint, Global_Polygon_ID mediumint, Admin_Unit_ID mediumint, Census_Code text(9), Hectares double, Non_Inland_Area double, Area_Type_Code text(2), Area_Type_Description text(25), Non_Area_Type_Code text(3), Non_Area_Type_Description text(36), fid int,PrimaryKey
    -> TestFilter
TestFilter
    DEFAULT_VALUE = <UNFILTERED>
    PASSED_TEST_GROUP_OUTPUT = FIRST
    TEST_LIST = "BOOL_OP,OR,COMPOSITE_TEST,""""""1"""""",TEST_CLAUSE,CASE_INSENSITIVE_TEST @Value(Name) CONTAINS South Wales",@Value(Name) CONTAINS "South Wales"
    @Value(Name) CONTAINS "South Wales" -> TestFilter_2
TestFilter_2
    DEFAULT_VALUE = <UNFILTERED>
    PASSED_TEST_GROUP_OUTPUT = FIRST
    TEST_LIST = "BOOL_OP,OR,COMPOSITE_TEST,""""""1"""""",TEST_CLAUSE,TEST @CoordSys() != EPSG:4326",@CoordSys() != EPSG:4326
    @CoordSys() != EPSG:4326 -> Reprojector_2
    <UNFILTERED> -> SpatialFilter [Filter]
    <UNFILTERED> -> Aggregator
Reprojector_2
    DEST = EPSG:4326
    INTERPOLATION_TYPE_NAME = Nearest Neighbor
    RASTER_CELL_SIZE = Preserve Cells
    RASTER_TOLERANCE = 0.0
    REPROJECTED -> SpatialFilter [Filter]
    REPROJECTED -> Aggregator
SpatialFilter
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    PASSED -> Clipper [CANDIDATE]
Aggregator
    ACCUM_ATTRS_NAME = Drop Incoming Attributes
    AGGREGATE_TYPE = Homogeneous Collection (If Possible)
    MODE = Geometry - Assemble One Level
    SEP = ,
    AGGREGATE -> Clipper [CLIPPER]
Clipper
    ADD_NODATA = YES
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    INSIDE -> RasterPaletteRemover
RasterPaletteRemover
    -> Exports2 (writer POSTGIS_RASTER_2)
Exports2 (writer POSTGIS_RASTER_2)

FME custom transformer FilePropertyExtractor
Extracts basic properties of a file or a directory and adds these attributes to the feature.
    _file_type
    : holds "File" or "Directory", which indicates whether the specified path is a file or a directory.
    _file_size
    : holds the size of file/directory in bytes (total of file sizes if directory)
    _file_atime
    : holds the time of last access.
    _file_mtime
    : holds the time of last modification.
    _file_ctime
    : holds the time of creation on some systems (like Windows), or the time of last metadata change on other systems (like Unix).
    You can specify the format of "_file_atime", "_file_mtime", and "_file_ctime" via the "Date/Time Format" parameter.
    The input feature will be output from the 
    <Rejected>
    port if the specified file/directory does not exist, the path indicates a symbolic link, or an unexpected error has occurred. 
    This transformer contains a Python script, which was tested with both Python 2.7 and Python 3.4 interpreter.
Parameters
    File/Directory Path
    :
    Specify the path of a file or a directory.
    Date/Time Format
    :
    Specify a date/datetime/time format that should be applied to the values of "_file_atime", "_file_mtime", and "_file_ctime". 
    The format syntax is the same as the DateFormatter. See the help doc on the transformer.

Parameters:
- PATH =   # File/Directory Path
- FMT = FME Date/Time (%Y%m%d%H%M%S)

Input (input)
    -> ParameterFetcher
ParameterFetcher
    ATTR_LIST = __filepropertyextractor.path {$(PATH)}
    -> PythonCaller
PythonCaller
    NEW_ATTRIBUTES = _file_type _file_size _file_atime _file_mtime _file_ctime __filepropertyextractor.error
    PYTHONSOURCE:
      # 2016-05-25, Takashi Iijima, Original Implementation
      # 2020-01-28, Takashi Iijima, Calculate Directory Size as Total File Sizes under the Directory; Changed Default Python Interpreter to 3.6+

      import fme, fmeobjects
      import os
      def extractFileProperty(feature):
          def get_dir_size(path):
              total = 0
              for p in os.listdir(path):
                  full_path = os.path.join(path, p)
                  if os.path.isfile(full_path):
                      total += os.path.getsize(full_path)
                  elif os.path.isdir(full_path):
                      total += get_dir_size(full_path)
              return total
          try:
              path = feature.getAttribute('__filepropertyextractor.path')
              if os.path.exists(path) and not os.path.islink(path):
                  s = os.stat(path)
                  if os.path.isdir(path):
                      feature.setAttribute('_file_type', 'Directory')
                      feature.setAttribute('_file_size', get_dir_size(path))
                  else:
                      feature.setAttribute('_file_type', 'File')
                      feature.setAttribute('_file_size', s.st_size)
                  feature.setAttribute('_file_atime', int(s.st_atime))
                  feature.setAttribute('_file_mtime', int(s.st_mtime))
                  feature.setAttribute('_file_ctime', int(s.st_ctime))
              else:
                  raise Exception('specified file/directory does not exist')
          except Exception as ex:
              feature.setAttribute('__filepropertyextractor.error', '%s' % ex)
    PYTHONSYMBOL = extractFileProperty
    -> Tester
Tester
    BOOL_OP = OR
    TEST_CLAUSE = TEST __filepropertyextractor.error ATTRIBUTE_IS_MISSING ""
    TEST_MODE = Automatic
    PASSED -> AttributeRemover
    FAILED -> AttributeRemover_2
AttributeRemover
    REMOVE_ATTRS = __filepropertyextractor.path,__filepropertyextractor.error
    -> DateFormatter
DateFormatter
    DATE_ATTR = _file_ctime,_file_mtime,_file_atime
    FMT = $(FMT)
    INVALID_DATE_VALUE = _FME_NO_OP_
    SRCFMT = %s
    -> Output (output)
Output (output)
AttributeRemover_2
    REMOVE_ATTRS = _file_size,_file_type,_file_ctime,__filepropertyextractor.path,_file_mtime,_file_atime
    -> AttributeRenamer
AttributeRenamer
    ATTR_TABLE = RENAME_SET_DEFAULT __filepropertyextractor.error > _rejected_reason
    -> <Rejected> (output)
<Rejected> (output)
